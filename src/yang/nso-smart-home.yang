module nso-smart-home {
  namespace "http://com/example/nsosmarthome";
  prefix nso-smart-home;

  import ietf-inet-types {
    prefix inet;
  }
  import tailf-common {
    prefix tailf;
  }
  import tailf-ncs {
    prefix ncs;
  }

  list nso-smart-home {
    description "This is an RFS skeleton service";

    key name;
    leaf name {
      tailf:info "Unique service id";
      tailf:cli-allow-range;
      type string;
    }

    // may replace this with other ways of refering to the devices.
    leaf-list device {
      type leafref {
        path "/ncs:devices/ncs:device/ncs:name";
      }
    }

    uses ncs:service-data;
    ncs:servicepoint nso-smart-home-servicepoint;

    tailf:action self-test {
      tailf:info "Perform self-test of the service";
      tailf:actionpoint nso-smart-home-self-test;
      output {
        leaf success {
          type boolean;
        }
        leaf message {
          type string;
          description
            "Free format message.";
        }
      }
    }
    // replace with your own stuff here
    leaf dummy {
      type inet:ipv4-address;
    }
  }
}
